(defun load-module (filename)
  (if (findfile filename)
    (load filename)
    (princ (strcat "\nWarning: " filename " not found"))
  )
)

(load-module "src/globals.lsp")
(load-module "src/settings.lsp")
(load-module "src/utilities.lsp")
(load-module "src/cmd_magi.lsp")
(load-module "src/cmd_xref.lsp")
(load-module "src/cmd_layer.lsp")
(load-module "src/cmd_misc.lsp")
(load-module "src/cmd_test.lsp")

(princ)
